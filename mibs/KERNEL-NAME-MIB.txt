KERNEL-NAME-MIB DEFINITIONS ::= BEGIN

IMPORTS
    OBJECT-TYPE, DISPLAY-HINT
        FROM SNMPv2-SMI
    TEXTUAL-CONVENTION
        FROM SNMPv2-TC;

-- Define the OID for kernel name
kernelNameMIB MODULE-IDENTITY
    LAST-UPDATED "202405070000Z"
    ORGANIZATION "My Company"
    CONTACT-INFO "you@example.com"
    DESCRIPTION "A simple custom MIB for getting kernel name"
    ::= { 1 3 6 1 4 1 112233 }

-- Define the OID for the kernel name
kernelName OBJECT-TYPE
    SYNTAX  DisplayString (SIZE (0..255))
    MAX-ACCESS  read-only
    STATUS  current
    DESCRIPTION "The system's kernel name (e.g., Linux, Darwin, etc.)"
    ::= { kernelNameMIB 3 }

END
