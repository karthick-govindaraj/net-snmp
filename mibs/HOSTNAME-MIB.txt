HOSTNAME-MIB DEFINITIONS ::= BEGIN

IMPORTS
    OBJECT-TYPE, MODULE-IDENTITY
        FROM SNMPv2-SMI
    TEXTUAL-CONVENTION, DisplayString
        FROM SNMPv2-TC;

-- Define the MIB module
hostnameMIB MODULE-IDENTITY
    LAST-UPDATED "202506250000Z"
    ORGANIZATION "My Company"
    CONTACT-INFO "you@example.com"
    DESCRIPTION "A custom MIB for getting and setting system hostname"
    REVISION "202506250000Z" 
    DESCRIPTION "Updated to support read-write operations"
    ::= { 1 3 6 1 4 1 112233 1 }

-- Define the hostname object  
hostname OBJECT-TYPE
    SYNTAX      DisplayString (SIZE (0..255))
    MAX-ACCESS  read-write
    STATUS      current
    DESCRIPTION 
        "The system's hostname.
         
         This object allows reading the current hostname and setting
         a new hostname. 
         
         When setting the hostname:
         - The hostname must be valid (1-255 characters)
         - Only alphanumeric characters, hyphens, and dots are allowed
         - The operation requires appropriate system privileges
         - Changes are applied immediately and persistently
         
         Valid hostname examples:
         - server1
         - web-server
         - db.example.com
         - test-machine-01"
    ::= { hostnameMIB 1 }

END
